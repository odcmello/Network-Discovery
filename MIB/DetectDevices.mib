DETECT-DEVICES-MIB DEFINITIONS ::= BEGIN

IMPORTS IpAddress, Counter, OBJECT-TYPE, Gauge, experimental FROM RFC1155-SMI 
DisplayString FROM RFC1213-MIB
TimeStamp FROM SNMPv2-TC;

discovery OBJECT IDENTIFIER ::={experimental 1}

Dispositivo ::= SEQUENCE {
	ipAddress DisplayString,
	macAddress DisplayString,
        fabricante DisplayString,
        status DisplayString,
        tipo DisplayString,
        horarioDescoberta TimeStamp
}

ipAddress OBJECT-TYPE
	SYNTAX DisplayString(SIZE(0..255))
	ACCESS read-only
	STATUS mandatory
	DESCRIPTION 
                "Endereco IP do dispositivo na rede"
	::= {dispositivo 1}

macAddress OBJECT-TYPE
        SYNTAX DisplayString(SIZE(0..255))  
        ACCESS read-only
        STATUS mandatory
        DESCRIPTION 
                "Endereco MAC do dispositivo na rede"
        ::= {dispositivo 2}

fabricante OBJECT-TYPE
        SYNTAX DisplayString(SIZE(0..255))  
        ACCESS read-only
        STATUS mandatory
        DESCRIPTION 
                "Nome do fabricante do dispositivo"
        ::= {dispositivo 3}

tipo OBJECT-TYPE
        SYNTAX DisplayString(SIZE(0..255))  
        ACCESS read-only
        STATUS mandatory
        DESCRIPTION 
                "Variavel que define se um dispositivo e roteador ou host"
        ::= {dispositivo 4}

status OBJECT-TYPE
        SYNTAX DisplayString(SIZE(0..255))  
        ACCESS read-only
        STATUS mandatory
        DESCRIPTION 
                "Estado atual do dispositivo, pode ser novo, antigo, desativado e reativado"
        ::= {dispositivo 5}

horarioDescoberta OBJECT-TYPE
        SYNTAX TimeStamp
        ACCESS read-only
        STATUS mandatory
        DESCRIPTION 
                "Horario da primeira descoberta do dispositivo na rede"
        ::= {dispositivo 6}

dispositivo OBJECT-TYPE
	SYNTAX Dispositivo
	ACCESS not-accessible
        STATUS mandatory
        DESCRIPTION 
                "Objeto do tipo Dispositivo, contendo endereco IP, endereco MAC, fabricante, estado atual, seu tipo e horario de descoberta"
	INDEX {macAddress}
	::= {dispositivosConectados 1}

dispositivosConectados OBJECT-TYPE
	SYNTAX SEQUENCE OF Dispositivo
	ACCESS not-accessible
        STATUS mandatory
        DESCRIPTION
                "Lista contendo todos os dispositivos que foram detectados e suas propriedades"
        ::= {discovery 1}

tempoPeriodicidade OBJECT-TYPE
	SYNTAX INTEGER
	ACCESS read-write
	STATUS mandatory
	DESCRIPTION 
                "Tempo definido pelo usuario entre cada deteccao de dispositivos na rede"
	::= {discovery 2}

ipAddressInitial OBJECT-TYPE
	SYNTAX DisplayString(SIZE(0..255))
	ACCESS read-only
	STATUS mandatory
	DESCRIPTION 
                "Substring do endereco IP do meu dispositivo, sera utilizado para identificar todos os IPs possiveis na rede"
	::= {discovery 3}

END
